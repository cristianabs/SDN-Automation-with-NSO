module ietf-network-slice {
  namespace "urn:ietf:params:xml:ns:yang:ietf-network-slice";
  prefix ietf-ns;

  import ietf-inet-types {
    prefix inet;
  }
  import ietf-yang-types {
    prefix yang;
  }
  import ietf-te-types {
    prefix te-types;
  }
  import tailf-common {
    prefix tailf;
  }
  import tailf-ncs {
    prefix ncs;
  }

  organization
    "IETF Traffic Engineering Architecture and Signaling (TEAS)
     Working Group";
  contact
    "WG Web:  <https://tools.ietf.org/wg/teas/>
     WG List:  <mailto:teas@ietf.org>
     Editor: Bo Wu <lana.wubo@huawei.com>
           : Dhruv Dhody <dhruv.ietf@gmail.com>
           : Reza Rokui <reza.rokui@nokia.com>
           : Tarek Saad <tsaad@juniper.net>";
  description
    "This module contains a YANG module for the IETF Network Slice.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2021-07-20 {
    description
      "initial version.";
    reference
      "RFC XXXX: A Yang Data Model for IETF Network Slice Operation";
  }

  /* Features */
  /* Identities */

  identity ns-isolation-type {
    description
      "Base identity for IETF Network slice isolation level.";
  }

  identity ns-isolation-shared {
    base ns-isolation-type;
    description
      "Shared resources (e.g. queues) are associated with the Network
       Slice traffic. Hence, the IETF network slice traffic can be
       impacted by effects of other services traffic sharing
       the same resources.";
  }

  identity ns-isolation-dedicated {
    base ns-isolation-type;
    description
      "Dedicated resources (e.g. queues) are associated with the
       Network Slice traffic. Hence, the IETF network slice traffic
       is isolated from other servceis traffic sharing the same
       resources.";
  }

  identity ns-security-type {
    description
      "Base identity for for IETF Network security level.";
  }

  identity ns-security-authenticate {
    base ns-security-type;
    description
      "IETF Network Slice requires authentication.";
  }

  identity ns-security-integrity {
    base ns-security-type;
    description
      "IETF Network Slice requires data integrity.";
  }

  identity ns-security-encryption {
    base ns-security-type;
    description
      "IETF Network Slice requires data encryption.";
  }

  identity ns-connectivity-type {
    description
      "Base identity for IETF Network Slice topology.";
  }

  identity any-to-any {
    base ns-connectivity-type;
    description
      "Identity for any-to-any IETF Network Slice topology.";
  }

  identity hub-spoke {
    base ns-connectivity-type;
    description
      "Identity for Hub-and-Spoke IETF Network Slice topology.";
  }

  identity custom {
    base ns-connectivity-type;
    description
      "Identity of a custom NS topology where Hubs can act as
       Spoke for certain parts of the network or Spokes as Hubs.";
  }

  identity endpoint-role {
    description
      "Base identity of a NSE role in an IETF Network Slice topology.";
  }

  identity any-to-any-role {
    base endpoint-role;
    description
      "Identity of any-to-any NS.";
  }

  identity spoke-role {
    base endpoint-role;
    description
      "A NSE is acting as a Spoke.";
  }

  identity hub-role {
    base endpoint-role;
    description
      "A NSE is acting as a Hub.";
  }

  identity ns-slo-metric-type {
    description
      "Base identity for IETF Network Slice SLO metric type.";
  }

  identity ns-slo-one-way-bandwidth {
    base ns-slo-metric-type;
    description
      "SLO bandwidth metric. Minimum guaranteed bandwidth between
       two endpoints at any time and is measured unidirectionally";
  }

  identity ns-slo-two-way-bandwidth {
    base ns-slo-metric-type;
    description
      "SLO bandwidth metric. Minimum guaranteed bandwidth between
       two endpoints at any time";
  }

  identity ns-slo-one-way-latency {
    base ns-slo-metric-type;
    description
      "SLO one-way latency is upper bound of network latency when
       transmitting between two endpoints. The metric is defined in
       RFC7679";
  }

  identity ns-slo-two-way-latency {
    base ns-slo-metric-type;
    description
      "SLO two-way latency is upper bound of network latency when
       transmitting between two endpoints. The metric is defined in
       RFC2681";
  }

  identity ns-slo-one-way-delay-variation {
    base ns-slo-metric-type;
    description
      "SLO one-way delay variation is defined by RFC3393, is the
       difference in the one-way delay between sequential packets
       between two endpoints.";
  }

  identity ns-slo-two-way-delay-variation {
    base ns-slo-metric-type;
    description
      "SLO two-way delay variation is defined by RFC5481, is the
       difference in the round-trip delay between sequential packets
       between two endpoints.";
  }

  identity ns-slo-one-way-packet-loss {
    base ns-slo-metric-type;
    description
      "SLO loss metric. The ratio of packets dropped to packets
       transmitted between two endpoints in one-way
       over a period of time as specified in RFC7680";
  }

  identity ns-slo-two-way-packet-loss {
    base ns-slo-metric-type;
    description
      "SLO loss metric. The ratio of packets dropped to packets
       transmitted between two endpoints in two-way
       over a period of time as specified in RFC7680";
  }

  identity ns-slo-availability {
    base ns-slo-metric-type;
    description
      "SLO availability level.";
  }

  identity ns-match-type {
    description
      "Base identity for IETF Network Slice traffic match type.";
  }

  identity ns-phy-interface-match {
    base ns-match-type;
    description
      "Use the physical interface as match criteria for the IETF
       Network Slice traffic.";
  }

  identity ns-vlan-match {
    base ns-match-type;
    description
      "Use the VLAN ID as match criteria for the IETF Network Slice
       traffic.";
  }

  identity ns-label-match {
    base ns-match-type;
    description
      "Use the MPLS label as match criteria for the IETF Network
       Slice traffic.";
  }

  identity peering-protocol-type {
    description
      "Base identity for NSE peering protocol type.";
  }

  identity peering-protocol-bgp {
    base peering-protocol-type;
    description
      "Use BGP as protocol for NSE peering with customer device.";
  }

  identity peering-static-routing {
    base peering-protocol-type;
    description
      "Use static routing for NSE peering with customer device.";
  }

  /*
   * Identity for availability-type
   */
  identity availability-type {
    description
      "Base identity from which specific availability types are
       derived.";
  }

  identity level-1 {
    base availability-type;
    description
      "level 1: 99.9999%";
  }

  identity level-2 {
    base availability-type;
    description
      "level 2: 99.999%";
  }

  identity level-3 {
    base availability-type;
    description
      "level 3: 99.99%";
  }

  identity level-4 {
    base availability-type;
    description
      "level 4: 99.9%";
  }

  identity level-5 {
    base availability-type;
    description
      "level 5: 99%";
  }

  /* typedef */

  typedef operational-type {
    type enumeration {
      enum up {
        value 0;
        description
          "Operational status UP.";
      }
      enum down {
        value 1;
        description
          "Operational status DOWN.";
      }
      enum unknown {
        value 2;
        description
          "Operational status UNKNOWN.";
      }
    }
    description
      "This is a read-only attribute used to determine the
       status of a particular element.";
  }

  typedef ns-monitoring-type {
    type enumeration {
      enum one-way {
        description
          "Represents one-way measurments monitoring type.";
      }
      enum two-way {
        description
          "represents two-way measurements monitoring type.";
      }
    }
    description
      "An enumerated type for monitoring on a IETF Network Slice
       connection.";
  }

  /* Groupings */

  grouping status-params {
    description
      "A grouping used to join operational and administrative status.";
    container status {
      description
        "A container for the administrative and operational state.";
      leaf admin-enabled {
        type boolean;
        description
          "The administrative status.";
      }
      leaf oper-status {
        type operational-type;
        config false;
        description
          "The operational status.";
      }
    }
  }

  grouping ns-match-criteria {
    description
      "A grouping for the IETF Network Slice match definition.";
    container ns-match-criteria {
      description
        "Describes the IETF Network Slice match criteria.";
      list ns-match-criterion {
        key "match-type";
        description
          "List of the IETF Network Slice traffic match criteria.";
        leaf match-type {
          type identityref {
            base ns-match-type;
          }
          description
            "Identifies an entry in the list of the IETF Network Slice
             match criteria.";
        }
        list values {
          key "index";
          description
            "List of match criteria values.";
          leaf index {
            type uint8;
            description
              "Index of an entry in the list.";
          }
          leaf value {
            type string;
            description
              "Describes the IETF Network Slice match criteria, e.g.
               IP address, VLAN, etc.";
          }
        }
      }
    }
  }

  grouping ns-connection-group-metric-bounds {
    description
      "Grouping of Network Slice metric bounds that
       are shared amongst multiple connections of a Network
       Slice.";
    leaf ns-slo-shared-bandwidth {
      type te-types:te-bandwidth;
      description
        "A limit on the bandwidth that is shared amongst
         multiple connections of an IETF Network Slice.";
    }
  }

  grouping ns-sles {
    description
      "Indirectly Measurable Objectives of a IETF Network
       Slice.";
    leaf-list security {
      type identityref {
        base ns-security-type;
      }
      description
        "The IETF Network Slice security SLE(s)";
    }
    leaf isolation {
      type identityref {
        base ns-isolation-type;
      }
      default "ns-isolation-shared";
      description
        "The IETF Network Slice isolation SLE requirement.";
    }
    leaf max-occupancy-level {
      type uint8 {
        range "1..100";
      }
      description
        "The maximal occupancy level specifies the number of flows to
         be admitted.";
    }
    leaf mtu {
      type uint16;
      units "bytes";
      mandatory true;
      description
        "The MTU specifies the maximum length in octets of data
         packets that can be transmitted by the NS. The value needs
         to be less than or equal to the minimum MTU value of
         all 'ep-network-access-points' in the NSEs of the NS. ";
    }
    container steering-constraints {
      description
        "Container for the policy of steering constraints
         applicable to IETF Network Slice.";
      container path-constraints {
        description
          "Container for the policy of path constraints
           applicable to IETF Network Slice.";
      }
      container service-function {
        description
          "Container for the policy of service function
           applicable to IETF Network Slice.";
      }
    }
  }

  grouping ns-metric-bounds {
    description
      "IETF Network Slice metric bounds grouping.";
    container ns-metric-bounds {
      description
        "IETF Network Slice metric bounds container.";
      list ns-metric-bound {
        key "metric-type";
        description
          "List of IETF Network Slice metric bounds.";
        leaf metric-type {
          type identityref {
            base ns-slo-metric-type;
          }
          description
            "Identifies an entry in the list of metric type
             bounds for the IETF Network Slice.";
        }
        leaf metric-unit {
          type string;
          mandatory true;
          description
            "The metric unit of the parameter. For example,
             s, ms, ns, and so on.";
        }
        leaf value-description {
          type string;
          description
            "The description of previous value. ";
        }
        leaf bound {
          type uint64;
          default "0";
          description
            "The Bound on the Network Slice connection metric. A
             zero indicate an unbounded upper limit for the
             specific metric-type.";
        }
      }
    }
  }

  grouping ep-peering {
    description
      "A grouping for the IETF Network Slice Endpoint peering.";
    container ep-peering {
      description
        "Describes NSE peering attributes.";
      list protocol {
        key "protocol-type";
        description
          "List of the NSE peering protocol.";
        leaf protocol-type {
          type identityref {
            base peering-protocol-type;
          }
          description
            "Identifies an entry in the list of NSE peering
             protocol type.";
        }
        list attribute {
          key "index";
          description
            "List of protocol attribute.";
          leaf index {
            type uint8;
            description
              "Index of an entry in the list.";
          }
          leaf attribute-description {
            type string;
            description
              "The description of the attribute. ";
          }
          leaf value {
            type string;
            description
              "Describes the value of protocol attribute, e.g.
               nexthop address, peer address, etc.";
          }
        }
      }
    }
  }
  grouping ep-network-access-points {
    description
      "Grouping for the endpoint network access definition.";
    container ep-network-access-points {
      description
        "List of network access points.";
      list ep-network-access-point {
        key "network-access-id";
        description
          "The IETF Network Slice network access points
           related parameters.";
        leaf network-access-id {
          type string;
          description
            "Uniquely identifier a network access point.";
        }
        leaf network-access-description {
          type string;
          description
            "The network access point description.";
        }
        leaf network-access-node-id {
          type string;
          description
            "The network access point node ID in the case of
             multi-homing.";
        }
        leaf network-access-tp-id {
          type string;
          description
            "The termination port ID of the EP network access
             point.";
        }
        leaf network-access-tp-ip {
          type inet:host;
          description
            "The IP address of the EP network access point.";
        }
        leaf mtu {
          type uint16;
          units "bytes";
          mandatory true;
          description
            "Maximum size in octets of a data packet that
             can traverse a NSE network access point. ";
        }
        /* Per ep-network-access-point rate limits */
        uses ns-rate-limit;
      }
    }
  }

  grouping endpoint-monitoring-parameters {
    description
      "Grouping for the endpoint monitoring parameters.";
    container ep-monitoring {
      config false;
      description
        "Container for endpoint monitoring parameters.";
      leaf incoming-utilized-bandwidth {
        type te-types:te-bandwidth;
        description
          "Incoming bandwidth utilization at an endpoint.";
      }
      leaf incoming-bw-utilization {
        type decimal64 {
          fraction-digits 5;
          range "0..100";
        }
        units "percent";
        mandatory true;
        description
          "To be used to define the bandwidth utilization
           as a percentage of the available bandwidth.";
      }
      leaf outgoing-utilized-bandwidth {
        type te-types:te-bandwidth;
        description
          "Outoing bandwidth utilization at an endpoint.";
      }
      leaf outgoing-bw-utilization {
        type decimal64 {
          fraction-digits 5;
          range "0..100";
        }
        units "percent";
        mandatory true;
        description
          "To be used to define the bandwidth utilization
           as a percentage of the available bandwidth.";
      }
    }
  }

  grouping common-monitoring-parameters {
    description
      "Grouping for link-monitoring-parameters.";
    leaf latency {
      type yang:gauge64;
      units "usec";
      description
        "The latency statistics per Network Slice connection.
         RFC2681 and RFC7679 discuss round trip times and one-way
         metrics, respectively";
    }
    leaf jitter {
      type yang:gauge32;
      description
        "The jitter statistics per Network Slice member
         as defined by RFC3393.";
    }
    leaf loss-ratio {
      type decimal64 {
        fraction-digits 6;
        range "0 .. 50.331642";
      }
      description
        "Packet loss as a percentage of the total traffic
         sent over a configurable interval. The finest precision is
         0.000003%. where the maximum 50.331642%.";
      reference
        "RFC 7810, section-4.4";
    }
  }

  grouping geolocation-container {
    description
      "A grouping containing a GPS location.";
    container location {
      description
        "A container containing a GPS location.";
      leaf altitude {
        type int64;
        units "millimeter";
        description
          "Distance above the sea level.";
      }
      leaf latitude {
        type decimal64 {
          fraction-digits 8;
          range "-90..90";
        }
        description
          "Relative position north or south on the Earth's surface.";
      }
      leaf longitude {
        type decimal64 {
          fraction-digits 8;
          range "-180..180";
        }
        description
          "Angular distance east or west on the Earth's surface.";
      }
    }
    // gps-location
  }

  // geolocation-container

  grouping ns-rate-limit {
    description
      "The Network Slice rate limit grouping.";
    container ep-rate-limit {
      description
        "Container for the asymmetric traffic control";
      leaf incoming-rate-limit {
        type te-types:te-bandwidth;
        description
          "The rate-limit imposed on incoming traffic.";
      }
      leaf outgoing-rate-limit {
        type te-types:te-bandwidth;
        description
          "The rate-limit imposed on outgoing traffic.";
      }
    }
  }

  grouping endpoint {
    description
      "IETF Network Slice endpoint related information";
    leaf ep-id {
      type string;
      description
        "unique identifier for the referred IETF Network
         Slice endpoint";
    }
    leaf ep-description {
      type string;
      description
        "endpoint name";
    }
    leaf ep-role {
      type identityref {
        base endpoint-role;
      }
      default "any-to-any-role";
      description
        "Role of the endpoint in the IETF Network Slice.";
    }
    uses geolocation-container;
    leaf node-id {
      type string;
      description
        "Uniquely identifies an edge node within the IETF slice
         network.";
    }
    leaf ep-ip {
      type inet:host;
      description
        "The address of the endpoint IP address.";
    }
    uses ns-match-criteria;
    uses ep-peering;
    uses ep-network-access-points;
    uses ns-rate-limit;
    /* Per NSE rate limits */
    uses status-params;
    uses endpoint-monitoring-parameters;
  }

  //ns-endpoint

  grouping ns-connection {
    description
      "The Network Slice connection is described in this container.";
    leaf ns-connection-id {
      type uint32;
      description
        "The Network Slice connection identifier";
    }
    leaf ns-connection-description {
      type string;
      description
        "The Network Slice connection description";
    }
    container src {
      description
        "the source of Network Slice link";
      leaf src-ep-id {
        type leafref {
          path "/network-slices/network-slice"
             + "/ns-endpoints/ns-endpoint/ep-id";
        }
        description
          "reference to source Network Slice endpoint";
      }
    }
    container dest {
      description
        "the destination of Network Slice link ";
      leaf dest-ep-id {
        type leafref {
          path "/network-slices/network-slice"
             + "/ns-endpoints/ns-endpoint/ep-id";
        }
        description
          "reference to dest Network Slice endpoint";
      }
    }
    uses ns-slo-sle-policy;
    /* Per connection ns-slo-sle-policy overrides
     * the per network slice ns-slo-sle-policy.
     */
    leaf monitoring-type {
      type ns-monitoring-type;
      description
        "One way or two way monitoring type.";
    }
    container ns-connection-monitoring {
      config false;
      description
        "SLO status Per network-slice endpoint to endpoint ";
      uses common-monitoring-parameters;
    }
  }

  //ns-connection

  grouping slice-template {
    description
      "Grouping for slice-templates.";
    container ns-slo-sle-templates {
      description
        "Contains a set of network slice templates to
         reference in the IETF network slice.";
      list ns-slo-sle-template {
        key "id";
        leaf id {
          type string;
          description
            "Identification of the Service Level Objective (SLO)
             and Service Level Expectation (SLE) template to be used.
             Local administration meaning.";
        }
        leaf template-description {
          type string;
          description
            "Description of the SLO &amp; SLE policy template.";
        }
        description
          "List for SLO and SLE template identifiers.";
      }
    }
  }

  /* Configuration data nodes */

  grouping ns-slo-sle-policy {
    description
      "Network Slice policy grouping.";
    choice ns-slo-sle-policy {
      description
        "Choice for SLO and SLE policy template.
         Can be standard template or customized template.";
      case standard {
        description
          "Standard SLO template.";
        leaf slo-sle-template {
          type leafref {
            path "/network-slices"
               + "/ns-slo-sle-templates/ns-slo-sle-template/id";
          }
          description
            "Standard SLO and SLE template to be used.";
        }
      }
      case custom {
        description
          "Customized SLO template.";
        container slo-sle-policy {
          description
            "Contains the SLO policy.";
          leaf policy-description {
            type string;
            description
              "Description of the SLO policy.";
          }
          uses ns-metric-bounds;
          uses ns-sles;
        }
      }
    }
  }

  container network-slices {
    description
      "IETF network-slice configurations";
    uses slice-template;
    list network-slice {
      key "ns-id";
      description
        "a network-slice is identified by a ns-id";
      leaf ns-id {
        type string;
        description
          "A unique network-slice identifier across an IETF NSC ";
      }
      leaf ns-description {
        type string;
        description
          "Give more description of the network slice";
      }
      leaf-list customer-name {
        type string;
        description
          "List of the customer that actually uses the slice.
           In the case that multiple customers sharing
           same slice service, e.g., 5G, customer name may
           help with operational management";
      }
      leaf ns-connectivity-type {
        type identityref {
          base ns-connectivity-type;
        }
        default "any-to-any";
        description
          "Network Slice topology.";
      }
      uses ns-slo-sle-policy;
      uses status-params;
      container ns-endpoints {
        description
          "Endpoints";
        list ns-endpoint {
        // servicepoint Adding
        uses ncs:service-data;
        ncs:servicepoint network-slice-ns-endpoint-servicepoint;
        // Fin addendum
          key "ep-id";
          uses endpoint;
          description
            "List of endpoints in this slice";
        }
      }
      container ns-connections {
        description
          "Connections container";
        list ns-connection {
          key "ns-connection-id";
          description
            "List of Network Slice connections.";
          uses ns-connection;
        }
      }
    }
    //ietf-network-slice list
  }
}
